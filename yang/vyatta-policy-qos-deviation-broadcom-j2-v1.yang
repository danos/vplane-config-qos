module vyatta-policy-qos-deviation-broadcom-j2-v1 {
	namespace "urn:vyatta.com:mgmt:vyatta-policy-qos-deviation-broadcom-j2:1";
	prefix vyatta-policy-qos-deviation-broadcom-j2;

	import vyatta-policy-v1 {
		prefix policy;
	}

	import vyatta-policy-qos-v1 {
		prefix qos;
	}

    organization "AT&T Inc.";
	contact
		"AT&T
          Postal: 208 S. Akard Street
                  Dallas, TX 75202
          Web: www.att.com";

	description
		"Copyright (c) 2020, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

         Deviations for QoS policies specific to the Broadcom Jericho-2 chip";

	revision 2020-03-31 {
		description "Initial revision of version 1.";
	}

	typedef j2-burst-size {
		description "Burst size in bytes for the shaper";
		type uint32 {
			range 4096..2093056;
			configd:help "Burst size in bytes for the shaper";
		}
	}

	deviation /policy:policy/qos:qos/qos:name/qos:shaper/qos:burst {
		deviate replace {
			type j2-burst-size;
		}
		deviate add {
			default "2093056";
		}
	}

	deviation /policy:policy/qos:qos/qos:name/qos:shaper/qos:profile/qos:burst {
		deviate replace {
			type j2-burst-size;
		}
		deviate add {
			default "2093056";
		}
	}

	deviation /policy:policy/qos:qos/qos:profile/qos:burst {
		deviate replace {
			type j2-burst-size;
		}
		deviate add {
			default "2093056";
		}
	}

	deviation /policy:policy/qos:qos/qos:mark-map/qos:dscp-group {
		deviate not-supported;
	}
}
