module vyatta-policy-qos-augment-v1 {
	namespace "urn:vyatta.com:mgmt:vyatta-policy-qos-augment:1";
	prefix vyatta-policy-qos-augment-v1;

	import configd-v1 {
		prefix configd;
	}
	import vyatta-policy-qos-groupings-v1 {
		prefix qos-groupings;
	}
	import vyatta-policy-v1 {
		prefix policy;
	}

	organization "AT&T Inc.";
	contact
		"AT&T
		 Postal: 208 S. Akard Street
		 Dallas, TX 75202
		 Web: www.att.com";

	description
		"Copyright (c) 2017-2019 AT&T Intellectual Property
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 This module provides the Quality of Service policy configuration.";

	revision 2020-08-27 {
		description "Change bandwidth default to auto so the platform
			     can determine the maximum range.";
	}

	revision 2017-09-15 {
		description "Initial revision for version 1.";
	}

	augment /policy:policy {
		container qos {
			configd:priority "400";
			description "Quality of Service (QoS)";
			configd:help "Quality of Service (QoS)";
			presence "QoS policy configured";
			uses qos-groupings:policy-list;
			uses qos-groupings:profile-list {
				refine profile/id {
					must "not(current() = /policy:policy/qos/name/shaper/profile/id)" {
						error-message "Global and local profile name must be different";
					}
				}
				refine profile/bandwidth {
					default "auto";
				}
			}
		}
	}
}
