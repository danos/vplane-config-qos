module vyatta-policy-qos-deviation-siad-v1 {
	namespace "urn:vyatta.com:mgmt:vyatta-policy-qos-deviation-siad:1";
	prefix vyatta-policy-qos-deviation-siad-v1;

	import vyatta-interfaces-v1 {
		prefix if;
	}

	import vyatta-interfaces-switch-v1 {
		prefix sw;
	}

	import vyatta-interfaces-dataplane-v1 {
		prefix interfaces-dataplane;
	}

	import vyatta-interfaces-dataplane-switch-v1 {
		prefix dp-sw;
	}

	import vyatta-policy-v1 {
		prefix policy;
	}

	import vyatta-interfaces-policy-v1 {
		prefix interfaces-policy;
	}

	import vyatta-interfaces-switch-policy-v1 {
		prefix sw-pol;
	}

	import vyatta-policy-qos-v1 {
		prefix qos;
	}

	import vyatta-policy-action-v1 {
		prefix action;
	}

	import vyatta-policy-qos-groupings-v1 {
		prefix qos-groupings;
	}

    organization "AT&T Inc.";
	contact
		"AT&T
          Postal: 208 S. Akard Street
                  Dallas, TX 25202
          Web: www.att.com";

	description
		"Copyright (c) 2019-2020, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Deviations for QoS policies on the SIAD platform";

	revision 2020-02-28 {
		description "Add configuration option to give burst size in
                             milliseconds.
                             Relax restriction on pipe queue to traffic class
                             mappings if ingress maps are used.
                             Disable time based burst configuration on Q-AX.";
	}

	revision 2019-06-20 {
		description "Add custom configd:must for slow must statements";
	}

	revision 2019-03-25 {
		description "Remove restriction on multiple queues in traffic classes 0-2.
                             Remove restriction on VLAN level policies per port.";
	}

	revision 2019-03-06 {
		description "Initial revision of version 1.";
	}

	deviation /if:interfaces/interfaces-dataplane:dataplane/interfaces-policy:policy {
		deviate not-supported;
	}

	deviation /if:interfaces/interfaces-dataplane:dataplane/interfaces-dataplane:vif/interfaces-policy:policy {
		deviate not-supported;
	}

	deviation /policy:policy/qos:qos/qos:name/qos:shaper/qos:profile {
		deviate replace {
			max-elements 1;
		}
	}

	deviation /policy:policy/qos:qos/qos:name/qos:shaper/qos:profile/qos:queue {
		deviate add {
			max-elements 8;
		}
	}

	deviation /policy:policy/qos:qos/qos:profile/qos:queue {
		deviate add {
			max-elements 8;
		}
	}

	deviation /policy:policy/qos:qos/qos:name/qos:shaper/qos:profile/qos:queue {
		deviate add {
			must "/policy:policy/qos:ingress-map or (count(../../../../qos:name/qos:shaper/qos:profile) + count(../../../../qos:profile) = " +
			     "count(../../../../qos:name/qos:shaper/qos:profile/qos:queue[qos:id=current()/qos:id and qos:traffic-class = current()/qos:traffic-class]) + " +
			     "count(../../../../qos:profile/qos:queue[qos:id=current()/qos:id and qos:traffic-class = current()/qos:traffic-class]))" {
				configd:must "verify-queue-id-and-traffic-class(.)";
				error-message "Traffic-class id for each pipe-queue id must be the same in all profiles";
			}
		}
	}

	deviation /policy:policy/qos:qos/qos:profile/qos:queue {
		deviate add {
			must "/policy:policy/qos:ingress-map or (count(../../qos:name/qos:shaper/qos:profile) + count(../../qos:profile) = " +
			     "count(../../qos:name/qos:shaper/qos:profile/qos:queue[qos:id=current()/qos:id and qos:traffic-class = current()/qos:traffic-class]) + " +
			     "count(../../qos:profile/qos:queue[qos:id=current()/qos:id and qos:traffic-class = current()/qos:traffic-class]))" {
				configd:must "verify-queue-id-and-traffic-class(.)";
				error-message "Traffic-class id for each pipe-queue id must be the same in all profiles";
			}
		}
	}

	deviation /policy:policy/qos:qos/qos:name/qos:shaper/qos:profile/qos:map/qos:dscp-group {
		deviate add {
			must "count(../../../../../qos:name/qos:shaper/qos:profile/qos:map) + " +
			     "count(../../../../../qos:profile/qos:map) = " +
			     "count(../../../../../qos:name/qos:shaper/qos:profile/qos:map/qos:dscp-group[qos:group-name = current()/qos:group-name and qos:to = current()/qos:to]) + " +
			     "count(../../../../../qos:profile/qos:map/qos:dscp-group[qos:group-name = current()/qos:group-name and qos:to = current()/qos:to])" {
				configd:must "verify-dscp-group-to-queue-mappings(.)";
				error-message "DSCP-group to queue mappings must be the same in all profiles";
			}
		}
	}

	deviation /policy:policy/qos:qos/qos:profile/qos:map/qos:dscp-group {
		deviate add {
			must "count(../../../qos:name/qos:shaper/qos:profile/qos:map) + " +
			     "count(../../../qos:profile/qos:map) = " +
			     "count(../../../qos:name/qos:shaper/qos:profile/qos:map/qos:dscp-group[qos:group-name = current()/qos:group-name and qos:to = current()/qos:to]) + " +
			     "count(../../../qos:profile/qos:map/qos:dscp-group[qos:group-name = current()/qos:group-name and qos:to = current()/qos:to])" {
				configd:must "verify-dscp-group-to-queue-mappings(.)";
				error-message "DSCP-group to queue mappings must be the same in all profiles";
			}
		}
	}

	deviation /policy:policy/qos:qos/qos:name/qos:shaper/qos:profile/qos:map/qos:pcp {
		deviate not-supported;
	}

	deviation /policy:policy/qos:qos/qos:profile/qos:map/qos:pcp {
		deviate not-supported;
	}

	deviation /policy:policy/qos:qos/qos:name/qos:shaper/qos:profile/qos:map/qos:dscp {
		deviate not-supported;
	}

	deviation /policy:policy/qos:qos/qos:profile/qos:map/qos:dscp {
		deviate not-supported;
	}

	deviation /policy:policy/qos:qos/qos:name/qos:shaper/qos:traffic-class/qos:queue-limit {
		deviate not-supported;
	}

	deviation /policy:policy/qos:qos/qos:name/qos:shaper/qos:profile/qos:queue/qos:wred-map {
		deviate not-supported;
	}

	deviation /policy:policy/qos:qos/qos:profile/qos:queue/qos:wred-map {
		deviate not-supported;
	}

	deviation /policy:policy/qos:qos/qos:mark-map {
		deviate replace {
			max-elements 1;
		}
	}

	deviation /policy:policy/qos:qos/qos:name/qos:shaper/qos:traffic-class/qos:random-detect {
		deviate not-supported;
	}

	deviation /policy:policy/qos:qos/qos:name/qos:shaper/qos:class {
		deviate not-supported;
	}

	deviation /policy:policy/action:action {
		deviate not-supported;
	}

	typedef siad-burst-size {
		description "Burst size in bytes for the shaper";
		type uint32 {
			range 1024..130048;
			configd:help "Burst size in bytes for the shaper";
		}
	}

	deviation /policy:policy/qos:qos/qos:name/qos:shaper/qos:burst {
		deviate replace {
			type siad-burst-size;
		}
		deviate add {
			default "16000";
		}
	}

	deviation /policy:policy/qos:qos/qos:name/qos:shaper/qos:profile/qos:burst {
		deviate replace {
			type siad-burst-size;
		}
		deviate add {
			default "16000";
		}
	}

	deviation /policy:policy/qos:qos/qos:profile/qos:burst {
		deviate replace {
			type siad-burst-size;
		}
		deviate add {
			default "16000";
		}
	}
}
