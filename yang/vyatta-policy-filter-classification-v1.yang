module vyatta-policy-filter-classification-v1 {
	namespace "urn:vyatta.com:mgmt:vyatta-policy-filter-classification:1";
	prefix policy-filter;

	import configd-v1 {
		prefix configd;
	}
	import vyatta-policy-v1 {
		prefix policy;
	}
	import vyatta-resources-v1 {
		prefix resources;
	}
	import vyatta-resources-packet-classifier-v1 {
		prefix res-gpc;
	}
	import vyatta-types-v1 {
		prefix vy-types;
	}
	import vyatta-interfaces-v1 {
		prefix if;
	}
	import vyatta-interfaces-dataplane-v1 {
		prefix interfaces-dataplane;
	}
	import vyatta-interfaces-policy-v1 {
		prefix interfaces-policy;
	}
	import vyatta-npf-v1 {
		prefix npf;
	}
	import vyatta-fw-types-v1 {
		prefix fw-types;
	}

	organization "AT&T Inc.";
	contact
		"AT&T
		 Postal: 208 S. Akard Street
		 Dallas, TX 75202, USA
		 Web: www.att.com";

	description
		"Copyright (c) 2021, AT&T Intellectual Property
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 This module provides common groupings for Quality of Service.";

	revision 2021-05-07 {
		description "Initial revision for version 1.";
	}

	feature generic-packet-classifier {
		description "Generic packet classifier support";
	}

	grouping marking-action {
		container mark {
			description "Packet marking action";
			configd:help "Packet marking action";

			leaf designation {
				description "Designation associated with packet";
				configd:help "Designation associated with packet";
				type uint32 {
					range 0..7;
				}
			}
			leaf drop-precedence {
				description "Drop precedence associated with packet";
				configd:help "Drop precedence associated with packet";
				type enumeration {
					enum "green" {
						description "Mark packets with drop precedence green";
						configd:help "Mark packets with drop precedence green";
					}
					enum "yellow" {
						description "Mark packets with drop precedence yellow";
						configd:help "Mark packets with drop precedence yellow";
					}
					enum "red" {
						description "Mark packets with drop precedence red";
						configd:help "Mark packets with drop precedence red";
					}
				}
			}
		}
	}

	grouping gpc-rules {
		list rules {
			description "Qos GPC rules";
			key "rule-number";
			leaf rule-number {
				description "The rule number generated internally";
				type fw-types:rule-number;
			}
			list matches {
				description "Classification criteria";
				key "match";
				leaf match {
					description "The match type";
					type string;
				}
				leaf value {
					description "The match value";
					type union {
						type string;
						type uint32;
					}
				}
			}
			leaf table-index {
				description "The table id incase of multiple instances";
				type uint16;
			}
			leaf orig-number {
				description "The rule number in the CLI";
				type uint16;
			}
			leaf result {
				description "The key matching classifier to actions";
				type string;
			}
			leaf designation {
				description "The queue designation";
				type uint8;
			}
			leaf colour {
				description "The packet priority on the queue";
				type string;
			}
			leaf decision {
				description "The pass or drop, pass is default";
				type string;
			}
			container police {
				description "The policer action";
				leaf bandwidth {
					description "The policer CIR bandwidth";
					type uint64;
				}
				leaf burst {
					description "The policer CIR burst";
					type uint64;
				}
				leaf excess-bandwidth {
					description "The policer EIR bandwidth";
					type uint64;
				}
				leaf excess-burst {
					description "The policer EIR burst";
					type uint64;
				}
				leaf packets {
					description "The packets passed by policer";
					type uint64;
				}
				leaf drops {
					description "The packets dropped by policer";
					type uint64;
				}
				leaf awareness {
					description "The policer colour awareness";
					type string;
				}
			}
			container counter {
				description "The counter for this rule";
				leaf counter-type {
					description "The counter type";
					type uint8;
				}
				leaf packets {
					description "The packet count";
					type uint64;
				}
				leaf bytes {
					description "The byte count";
					type uint64;
				}
			}
		}
	}

	grouping gpc-feature {
		list tables {
			description "GPC tables";
			key "table-id";
			leaf table-id {
				description "The key ifname/dir/AF";
				type string;
			}
			list table-names {
				description "List of GPC tables";
				key "name";
				leaf name {
					description "The table name";
					type string;
				}
				leaf table-index {
					description "The table identifier";
					type uint16;
				}
			}
			uses gpc-rules;
		}
		list counters {
			description "List of named counters";
			key "name";
			leaf name {
				description "The name of the counter";
				type string;
			}
			leaf packets {
				description "The packet count";
				type uint64;
			}
			leaf bytes {
				description "The byte count";
				type uint64;
			}
		}
	}

	grouping gpc-tables {
		list features {
			description "GPC features";
			key "type";
			leaf type {
				description "GPC feature type";
				type string;
			}
			uses gpc-feature;
		}
	}

	rpc get-filter-classification-information {
		description "Get information on Qos GPC.";
		input {
			leaf feature {
				description "Name of the feature, qos in this case.";
				type string;
			}
			leaf interface {
				description "The name of the interface we want state from";
				type string;
			}
		}
		output {
			container gpc {
				description "QOS GPC state and statistical information";

				uses gpc-tables;
			}
		}
	}

	grouping policing-action {
		container police {
			description "Packet policer action";
			configd:help "Packet policer action";
			presence "Result maps to policer action; mandatory child nodes when configured";
			leaf bandwidth {
				type npf:bandwidth-suffix;
				description "Bandwidth limit in bytes/second";
				configd:help "Bandwidth limit in bytes/second";
				mandatory true;
			}

			leaf excess-bandwidth {
				type npf:bandwidth-suffix;
				description "Excess bandwidth limit in bytes/second";
				configd:help "Excess bandwidth limit in bytes/second";
				must "../bandwidth" {
					error-message "Excess bandwidth requires bandwidth configuration";
				}
			}
			leaf burst {
				type npf:burst-size;
				description "Burst size in bytes";
				configd:help "Burst size in bytes";
			}
			leaf excess-burst {
				type npf:burst-size;
				description "Excess burst size in bytes";
				configd:help "Excess burst size in bytes";
				must "../excess-bandwidth" {
					error-message "Excess burst requires excess bandwidth configuration";
				}
			}
			leaf colour-awareness {
				description "Policer colour awareness";
				configd:help "Policer colour awareness";
				type enumeration {
					enum "colour-aware" {
						description "Packets entering policer cannot have drop-precedence decreased";
						configd:help "Packets entering policer cannot have drop-precedence decreased";
					}
					enum "colour-unaware" {
						description "Packets entering policer are treated as drop-precedence green";
						configd:help "Packets entering policer are treated as drop-precedence green";
					}
				}
				mandatory true;
			}
		}
	}

	grouping res-actions {
		list result {
			key "result";
			description "Mapping of result to actions";
			configd:help "Mapping of result to actions";
			min-elements 1;
			leaf result {
				description  "Classifier result";
				configd:help "Classifier result";
				type leafref {
					path "/resources:resources/res-gpc:packet-classifier/res-gpc:classifier/res-gpc:results/res-gpc:result";
				}
			}
			container action {
				description "Actions";
				configd:help "Actions";
				presence "Actions applied to packet";
				uses marking-action;
				uses policing-action;
			}
		}
	}

	grouping filter-classification-list {
		list group {
			description "Filter classification group";
			configd:help "Filter classification group";
			key "group-name";
			min-elements 1;
			leaf group-name {
				description  "Group name";
				configd:help "Group name";
				type vy-types:alpha-numeric {
					configd:help "Group name";
					length 1..16;
				}
			}
			leaf description {
				description  "Group description";
				configd:help "Group description";
				type string;
			}
			container counters {
				description  "Configure counters";
				configd:help "Configure counters";
				presence "Group counter criteria; mandatory child nodes when configured";
				leaf sharing {
					description  "Configured counter sharing";
					configd:help "Configured counter sharing";
					mandatory true;
					type enumeration {
						enum "per-interface" {
							description  "Unique counter applied to each interface";
							configd:help "Unique counter applied to each interface";
						}
					}
				}
				leaf type {
					description  "Configure counter type";
					configd:help "Configure counter type";
					type enumeration {
						enum auto-per-rule {
							description  "Auto per rule";
							configd:help "Auto per rule";
						}
					}
					default "auto-per-rule";
				}
			}
			uses res-gpc:gpc-import-classifiers;
			uses res-gpc:gpc-classify;
			must "count(classify) < 2" {
				error-message "Only one classifier may be used";
			}
			container map {
				uses res-actions;
			}
		}
	}

	augment /policy:policy {
		if-feature generic-packet-classifier;
		container filter-classification {
			description "Classification filter results";
			configd:help "Classification filter results";
			presence "Map generic filter results to actions";
			uses filter-classification-list;
		}
	}

	augment /if:interfaces/interfaces-dataplane:dataplane/interfaces-policy:policy {
		if-feature generic-packet-classifier;
		leaf-list filter-classification-group {
			configd:help "QoS filter classification groups for interface, max 1 per traffic-type";
			description "QoS filter classification group for interface, max 1 per traffic type";
			type leafref {
				path "/policy:policy/filter-classification/group/group-name";
			}
			max-elements 2;
		}
	}
}
