module vyatta-policy-qos-uplink-v1 {
	namespace "urn:vyatta.com:mgmt:vyatta-policy-qos-uplink:1";
	prefix vyatta-policy-qos-uplink-v1;

	import configd-v1 {
		prefix configd;
	}
	import vyatta-interfaces-policy-uplink-v1 {
		prefix interfaces-policy-uplink;
	}
	import vyatta-interfaces-uplink-v1 {
		prefix interfaces-uplink;
	}
	import vyatta-interfaces-v1 {
		prefix if;
	}
	import vyatta-policy-qos-augment-v1 {
		prefix qos-augment;
	}
	import vyatta-policy-v1 {
		prefix policy;
	}

	organization "AT&T Inc.";
	contact
		"AT&T
		 Postal: 208 S. Akard Street
		 Dallas, TX 75202
		 Web: www.att.com";

	description
		"Copyright (c) 2017-2019 AT&T Intellectual Property
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 This module provides the Quality of Service configuration for uplink interfaces.";

	revision 2019-08-30 {
		description "Move to VCI for commit processing.";
	}

	revision 2018-09-13 {
		description "Separate the validation and commit steps
			     to avoid connnecting to Vplaned for each
			     validation.";
	}

	revision 2017-09-15 {
		description "Initial revision for version 1.";
	}

	augment /if:interfaces/interfaces-uplink:uplink/interfaces-policy-uplink:policy {
		leaf qos {
			type leafref {
				path "/policy:policy/qos-augment:qos/qos-augment:name/qos-augment:id";
			}
			description "QoS policy name for interface";
			configd:help "QoS policy name for interface";
			configd:validate "qos-validate.pl --validate-binding $VAR(../../@) 0";
		}
	}
}
