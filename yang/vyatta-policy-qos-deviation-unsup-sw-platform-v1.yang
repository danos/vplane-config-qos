module vyatta-policy-qos-deviation-unsup-sw-platform-v1 {
	namespace "urn:vyatta.com:mgmt:vyatta-policy-qos-deviation-unsup-sw-platform:1";
	prefix vyatta-policy-qos-deviation-unsup-sw-platform-v1;

	import vyatta-interfaces-v1 {
		prefix if;
	}

	import vyatta-interfaces-switch-v1 {
		prefix sw;
	}

	import vyatta-interfaces-dataplane-v1 {
		prefix interfaces-dataplane;
	}

	import vyatta-interfaces-dataplane-switch-v1 {
		prefix dp-sw;
	}

	import vyatta-policy-v1 {
		prefix policy;
	}

	import vyatta-interfaces-policy-v1 {
		prefix interfaces-policy;
	}

	import vyatta-interfaces-switch-policy-v1 {
		prefix sw-pol;
	}

	import vyatta-policy-qos-v1 {
		prefix qos;
	}

	import vyatta-policy-action-v1 {
		prefix action;
	}

    organization "AT&T Inc.";
	contact
		"AT&T
          Postal: 208 S. Akard Street
                  Dallas, TX 75202
          Web: www.att.com";

	description
		"Copyright (c) 2019-2020, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Deviations to remove QoS on unsupported switch platforms";

	revision 2020-03-19 {
		description "Added license.";
	}
	revision 2019-10-30 {
		description "Initial revision of version 1.";
	}

	deviation /if:interfaces/interfaces-dataplane:dataplane/interfaces-policy:policy/qos:qos {
		deviate not-supported;
	}

	deviation /if:interfaces/interfaces-dataplane:dataplane/interfaces-dataplane:vif/interfaces-policy:policy/qos:qos {
		deviate not-supported;
	}

	deviation /if:interfaces/interfaces-dataplane:dataplane/dp-sw:switch-group/dp-sw:port-parameters/sw-pol:policy/qos:qos {
		deviate not-supported;
	}

	deviation /if:interfaces/interfaces-dataplane:dataplane/dp-sw:switch-group/dp-sw:port-parameters/dp-sw:vlan-parameters/dp-sw:qos-parameters {
		deviate not-supported;
	}

	deviation /if:interfaces/sw:switch/sw:default-port-parameters/sw:vlan-parameters/sw:qos-parameters {
		deviate not-supported;
	}

	deviation /policy:policy/qos:qos {
		deviate not-supported;
	}

	deviation /policy:policy/action:action {
		deviate not-supported;
	}
}
