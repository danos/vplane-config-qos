module vyatta-policy-qos-deviation-ufi-s9500-30xs-v1 {
	namespace "urn:vyatta.com:mgmt:vyatta-policy-qos-deviation-ufi-s9500-30xs:1";
	prefix vyatta-policy-qos-deviation-ufi-s9500-30xs-v1;

	import vyatta-interfaces-v1 {
		prefix if;
	}

	import vyatta-interfaces-dataplane-v1 {
		prefix interfaces-dataplane;
	}

	import vyatta-policy-v1 {
		prefix policy;
	}

	import vyatta-interfaces-policy-v1 {
		prefix interfaces-policy;
	}

	import vyatta-policy-qos-v1 {
		prefix qos;
	}

	import vyatta-policy-action-v1 {
		prefix action;
	}

    organization "Ciena Corporation";
	contact
	    "Web URL: https://www.ciena.com/
	     Postal:  7035 Ridge Road
		      Hanover, Maryland 21076
		      U.S.A.
	     Phone:   +1 800-921-1144
	     Fax:     +1 410-694-5750";

	description
		"Copyright (c) 2021, Ciena Corporation, All Rights Reserved.

		 Copyright (c) 2020, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Deviations for QoS policies on the UFI S9500-30XS platform";

	revision 2021-11-17 {
		description "Delete the must from wred-map-bytes max-threshold.";
	}

	revision 2020-03-26 {
		description "Allow QoS on dataplane interfaces and VIFs.";
	}

	revision 2020-03-09 {
		description "Initial revision of version 1.";
	}

	deviation /policy:policy/qos:qos/qos:name/qos:shaper/qos:profile/qos:map/qos:pcp {
		deviate not-supported;
	}

	deviation /policy:policy/qos:qos/qos:profile/qos:map/qos:pcp {
		deviate not-supported;
	}

	deviation /policy:policy/qos:qos/qos:name/qos:shaper/qos:profile/qos:map/qos:dscp {
		deviate not-supported;
	}

	deviation /policy:policy/qos:qos/qos:profile/qos:map/qos:dscp {
		deviate not-supported;
	}

	deviation /policy:policy/qos:qos/qos:name/qos:shaper/qos:class {
		deviate not-supported;
	}

	deviation /policy:policy/action:action {
		deviate not-supported;
	}

	deviation /policy:policy/qos:qos/qos:name/qos:shaper/qos:profile/qos:queue/qos:wred-map-bytes/qos:dscp-group/qos:max-threshold {
		deviate delete {
			must "not(../min-threshold) or (../max-threshold > ../min-threshold)" {
				error-message "min-threshold must be less than" +
					      " max-threshold";
			}
		}
	}
}
