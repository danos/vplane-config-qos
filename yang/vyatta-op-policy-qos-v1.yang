module vyatta-op-policy-qos-v1 {
	namespace "urn:vyatta.com:mgmt:vyatta-op-policy-qos:1";
	prefix vyatta-op-policy-qos-v1;

	import vyatta-opd-extensions-v1 {
		prefix opd;
	}
	import vyatta-op-clear-v1 {
		prefix clear;
	}
	import vyatta-op-show-v1 {
		prefix show;
	}
	import vyatta-op-policy-pbr-v1 {
	        prefix policy;
	}
	import vyatta-op-monitor-v1 {
	        prefix monitor;
	}

	organization "Ciena Corporation";
	contact
		"Web URL: https://www.ciena.com/
		Postal:  7035 Ridge Road
				Hanover, Maryland 21076
				U.S.A.
		Phone:   +1 800-921-1144
		Fax:     +1 410-694-5750";

	description
		"Copyright (c) 2021, Ciena Corporation, All Rights Reserved.

		 Copyright (c) 2017-2021, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 YANG module for policy QoS operational mode commands.";

	revision 2021-11-17 {
		description "New commands: show/monitor policy qos summary";
	}

	revision 2021-03-29 {
		description "Add the filter-classification option to the
			     op-mode commands.";
	}

	revision 2020-06-07 {
		description "Update the show commands to support the
			    egress map commands";
	}
	revision 2020-04-28 {
		description "Give QoS show commands privilege for operators
			    as they access a socket to the dataplane";
	}
	revision 2020-01-25 {
		description "Update the show commands to support the
			    ingress map commands and add a feature flag";
	}
	revision 2019-12-16 {
		description "Add support for showing buffer congestion information:
			    buffer-threshold, buffer-utilization and buffer-utilization
			    errors";
	}
	revision 2019-02-25 {
		description "Fix option name confusion between yang and perl
			    scripts.
			    Add support for show queuing <interface> map
			    mark-map.
			    Add support for 64-bit clear/show policy qos
			    commands.
			    Add platform subcommands.";
	}
	revision 2018-05-23 {
		description "Convert show queuing command to use yang.";
	}
	revision 2017-12-09 {
		description "Initial support for clear queuing command.";
	}

	feature gpc {
		description "General Packet Classifier command support";
	}

	feature show-platform {
		description "QoS platform show command support";
	}

	feature ingress-map {
		description "QoS ingress-map show command support";
	}

	feature egress-map {
		description "QoS egress-map show command support";
	}

	opd:augment /clear:clear {

		opd:command queuing {
			opd:help "Clear QoS queuing counters";
			opd:on-enter "qos-clear-counters.pl --clear-all";
			opd:privileged true;
			opd:inherit "inherit privileged statement" {
				opd:privileged true;
			}

			opd:argument interface-name {
				opd:help "Interface name";
				type string;
				opd:allowed "qos-clear-counters.pl --if-list";
				opd:on-enter "qos-clear-counters.pl --clear-if=$3";
			}
		}
	}

	opd:augment /clear:clear/policy:policy {

		opd:command qos {
			opd:help "Clear QoS queuing counters";
			opd:on-enter "qos-clear-counters.pl --clear-all";
			opd:privileged true;
			opd:inherit "inherit privileged statement" {
				opd:privileged true;
			}

			opd:argument interface-name {
				opd:help "Interface name";
				type string;
				opd:allowed "qos-clear-counters.pl --if-list";
				opd:on-enter "qos-clear-counters.pl --clear-if=$4";
			}
		}
	}

	grouping qos-interface {
		opd:command class {
			opd:help "Show specified dataplane interface match information";
			opd:on-enter "show-queueing.pl --class $3";
		}
		opd:command map {
			opd:help "Show dataplane queue mapping";

			opd:command dscp {
				opd:help "Show dataplane DSCP to queue information";
				opd:on-enter "show-queueing.pl --dscp $3";
			}
			opd:command pcp {
				opd:help "Show dataplane priority code point to queue information";
				opd:on-enter "show-queueing.pl --cos $3";
			}
			opd:command mark {
				opd:help "Show dataplane dscp-to-pcp marking information";
				opd:on-enter "show-queueing.pl --mark $3";
			}
		}
		opd:command brief {
			opd:help "Show brief queuing summary";
			opd:on-enter "show-queueing.pl --brief $3";
		}
		opd:command filter-classification {
			if-feature gpc;
			opd:help "Show the filter-classification used in the dataplane for an interface";
			opd:on-enter "show_gpc_rpc.py $4";
		}
	}

	grouping qos-interface-64 {
		opd:command class {
			opd:help "Show specified dataplane interface match information";
			opd:on-enter "show-queueing.pl --64 --class $4";
		}
		opd:command map {
			opd:help "Show dataplane queue mapping";

			opd:command dscp {
				opd:help "Show dataplane DSCP to queue information";
				opd:on-enter "show-queueing.pl --dscp $4";
			}
			opd:command platform {
				if-feature show-platform;
				opd:help "Show platform map information";
				opd:command egress {
					opd:help "Show platform egress remark map information";
					opd:on-enter "show-queueing.pl --platmapegr $4";
				}
				opd:command ingress {
					opd:help "Show platform ingress classification map information";
					opd:on-enter "show-queueing.pl --platmaping $4";
				}
			}
			opd:command pcp {
				opd:help "Show dataplane priority code point to queue information";
				opd:on-enter "show-queueing.pl --cos $4";
			}
			opd:command mark {
				opd:help "Show dataplane dscp-to-pcp marking information";
				opd:on-enter "show-queueing.pl --mark $4";
			}
		}
		opd:command brief {
			opd:help "Show brief queuing summary";
			opd:on-enter "show-queueing.pl --64 --brief $4";
		}
		opd:command ingress-map {
			if-feature ingress-map;
			opd:help "Show the ingress-map used in the dataplane";
			opd:on-enter "show-queueing.pl --ingress-maps $4";
		}
		opd:command egress-map {
			if-feature egress-map;
			opd:help "Show the egress-map used in the dataplane";
			opd:on-enter "show-queueing.pl --egress-maps $4";
		}
		opd:command filter-classification {
			if-feature gpc;
			opd:help "Show the filter-classification used in the dataplane for an interface";
			opd:on-enter "show_gpc_rpc.py $4";
		}
	}

	opd:augment /show:show {

		opd:command queuing {
			opd:help "Show dataplane queuing summary";
			opd:on-enter "show-queueing.pl --summary";
			opd:privileged true;
			opd:inherit "inherit privileged statement" {
				opd:privileged true;
			}

			opd:command class {
				opd:help "Show dataplane matching summary";
				opd:on-enter "show-queueing.pl --class";
			}

			opd:argument interface-name {
				opd:help "Show dataplane interface queuing summary";
				opd:allowed "vyatta-interfaces.pl --show=dataplane,vhost,bonding";
				opd:on-enter "show-queueing.pl $3";
				type string;

				uses qos-interface;
			}
		}
	}

	opd:augment /show:show/policy:policy {

		opd:command qos {
			opd:help "Show dataplane queuing summary";
			opd:on-enter "show-queueing.pl --64 --summary";
			opd:privileged true;
			opd:inherit "inherit privileged statement" {
				opd:privileged true;
			}

			opd:command platform {
				if-feature show-platform;
				opd:help "Show platform DSCP to queue information";
				opd:on-enter "show-queueing.pl --platinfo";

				opd:command buffer-threshold {
					opd:help "Show buffer congestion threshold";
					opd:on-enter "show-ext-buf.pl --threshold";
				}

				opd:command buffer-utilization {
					opd:help "Show current buffer utilization";
					opd:on-enter "show-ext-buf.pl --utilization";

					opd:command errors {
						opd:help "Show buffer errors";
						opd:on-enter "show-queueing.pl --buffer-errors";
					}
				}
			}

			opd:command class {
				opd:help "Show dataplane matching summary";
				opd:on-enter "show-queueing.pl --64 --class";
			}

			opd:argument interface-name {
				opd:help "Show dataplane interface queuing summary";
				opd:allowed "vyatta-interfaces.pl --show=dataplane,vhost,bonding,switch";
				opd:on-enter "show-queueing.pl --64 $4";
				type string;

				uses qos-interface-64;
			}

			opd:command ingress-maps {
				if-feature ingress-map;
				opd:help "Show all ingress-maps downloaded to the dataplane";
				opd:on-enter "show-queueing.pl --ingress-maps";
			}

			opd:command egress-maps {
				if-feature egress-map;
				opd:help "Show all egress-maps downloaded to the dataplane";
				opd:on-enter "show-queueing.pl --egress-maps";
			}

			opd:command filter-classification {
				if-feature gpc;
				opd:help "Show the filter-classification used in the dataplane";
				opd:on-enter "show_gpc_rpc.py";
			}

			opd:command summary {
				opd:help "Show dataplane queuing summary";
				opd:on-enter "show_queueing.py --drop-summary";
			}
		}
	}

	opd:augment /monitor:monitor {

		opd:command policy {
			opd:command qos {
				opd:help "Monitor dataplane queuing information";
				opd:on-enter "show-queueing.pl --64 --monitor";
				opd:privileged true;

				opd:command summary {
					opd:help "Show dataplane queuing summary";
					opd:on-enter "show_queueing.py --monitor --drop-summary";
				}
			}
		}
	}

}
